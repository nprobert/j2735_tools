--
-- Terms and Conditions and User License Agreement - Download and Use of ASN File
-- 
-- Copyright: Each ASN File contained herein ("File") is copyrighted and all
-- rights, title, and interest in and to each File are owned by SAE. The 
-- license contained herein applies to each File and each reference in this license
-- to "the File" or "this File" shall be construed to include each and any ASN File
-- contained herein. No rights therein are granted except as set forth in this
-- License. Any copying, transmission, modification or reproduction of the File or
-- the copyrighted material within it, in part or in whole, except as herein
-- permitted is cause for revocation of this License.
-- 
-- License: SAE International ("SAE") hereby grants to you, as an individual or as
-- a single corporate entity, a limited nonexclusive, nontransferable right to
-- download this File in an electronic format for your individual use or use by
-- a single corporate entity on one computer. One hard copy of the File can also
-- be printed for individual use or use by a single corporate entity. SAE also
-- hereby grants to you the nonexclusive, nontransferable right to use this File
-- and create derivative works using this File for your own or your own corporate
-- entity's research purposes and in the design, creation, manufacture, distribution,
-- and use of your own products. For purposes of clarification, derivative works
-- permitted under this license include derivative works or source code that do not
-- include or incorporate this File. The derivative work may use the File to create
-- source code and corresponding software programs.  Notwithstanding the foregoing,
-- you agree that you must obtain a license from SAE to create any derivative works
-- which incorporate this File or its contents.
--
-- SAE also hereby grants to you the nonexclusive, nontransferable right to copy,
-- reproduce, distribute to others the derivative works from the use of the content
-- of this File or portions thereof in or as part of your company's products.
-- You must only license, and not otherwise sell or transfer, the products, software,
-- and software documentation that incorporates content from this File, and you must
-- prohibit any licensees or others from transferring, copying, or extracting the
-- contents of this File thereof for use in their own or others' software or products.
--
-- Other than as expressly permitted herein, this File may not be copied in whole in
-- any form for distribution to other users or other computers, including without
-- limitation to other individuals or users within your own corporate entity or
-- outside your corporate entity.  This license prohibits the end user from posting
-- or distributing content via any public forum or as open access content.  If other
-- individuals in or outside your corporate entity or different cooperate entities,
-- whether related or not to your corporate entity, wish to download or copy this
-- File, they must purchase a separate individual license to do so. 
-- 
-- This File is licensed "AS IS" to you and you do hereby hold SAE harmless from your
-- use of the File or the creative or use of derivative works thereof, and you agree
-- to indemnify SAE from any and all claims or damages caused by your use,
-- reproduction, distribution to others, or application of this File or any
-- derivative works therefrom.  SAE may amend the terms of and conditions of
-- this License or cancel this License at any time in its sole discretion and
-- for any reason by reasonable notice, including without limitation by posting
-- revised terms on its website.  
--
-- General: Files that have been successfully downloaded cannot be returned for
-- refund or credit. This Agreement is the complete and exclusive statement of the
-- agreement between you and SAE and supersedes any and all prior agreements or
-- understandings, either written or oral, concerning the subject of this Agreement.
-- Any modifications must be in writing and signed by the parties.
-- 
-- Notice to Resellers: Authorized resellers of SAE Files may download this File on
-- behalf of their customers and forward it directly, unopened, to their customers
-- provided their customers agree to abide by the terms of this License. Resellers
-- may not otherwise copy, transmit, modify or reproduce this File.
-- 
-- This license will remain in effect for the life of the standards associated with
-- the File unless otherwise amended or cancelled by SAE in its sole discretion.
-- In the event that the associated standard is cancelled or recalled due to interest
-- of public safety, the aforementioned License will be rescinded as well. This 
-- License shall terminate upon violation of any of its terms.
--
-- (C)2024 SAE International.  All rights reserved.  SAE International retains the
-- right to entertain or negotiate requests for customized distribution agreements
-- for multi-user or corporate use and / or distribution. Requests should be submitted
-- to customerservice@sae.org.
--

--
-- Use of this module defined in SAE J2735 
-- Latest document release for this module is Nov 2022
-- Filename: J2735-MapData-2024-rel-v1.1.asn 
--

MapData
{joint-iso-itu-t (2) country (16) us (840) organization (1) sae (114566)
v2x-communications (1) technical-committees (1) v2x-core (5) technical-reports (1)
j2735 (2735) part-0 (0) asn1-module (1) mapData (8) version-1 (1) version-minor-1 (1)}

DEFINITIONS AUTOMATIC TAGS ::=
BEGIN

IMPORTS 
	Reg-MapData, 
	Reg-GenericLane, 
	Reg-IntersectionGeometry, 
	Reg-LaneAttributes, 
	Reg-SignalControlZone, 
	Reg-RestrictionUserType, 
	Reg-RoadSegment
		FROM REGION {joint-iso-itu-t (2) country (16) us (840) organization (1) sae (114566)
		v2x-communications (1) technical-committees (1) v2x-core (5) technical-reports (1)
		j2735 (2735) part-0 (0) asn1-module (1) region (2) 
		version-1 (1) version-minor-1 (1)} WITH SUCCESSORS
	MinuteOfTheYear, 
	MsgCount, 
	RegionalExtension, 
	LaneID, 
	IntersectionReferenceID, 
	SignalGroupID, 
	RestrictionClassID, 
	LaneConnectionID, 
	DescriptiveName, 
	ApproachID, 
	NodeListXY, 
	Position3D, 
	LaneWidth, 
	SpeedLimitList, 
	RoadSegmentReferenceID,
    RoadAuthorityID
		FROM Common {joint-iso-itu-t (2) country (16) us (840) organization (1) sae (114566)
		v2x-communications (1) technical-committees (1) v2x-core (5) technical-reports (1)
		j2735 (2735) part-0 (0) asn1-module (1) common (38) 
		version-1 (1) version-minor-1 (1)} WITH SUCCESSORS;





MapData ::= SEQUENCE {
   timeStamp         MinuteOfTheYear OPTIONAL, 
   msgIssueRevision  MsgCount,        
   layerType         LayerType OPTIONAL,
   layerID           LayerID  OPTIONAL,
   intersections     IntersectionGeometryList OPTIONAL,
                     -- All Intersection definitions 
   roadSegments      RoadSegmentList OPTIONAL,
                     -- All roadway descriptions
  
   dataParameters    DataParameters OPTIONAL,
                     -- Any meta data regarding the map contents
   
   restrictionList   RestrictionClassList OPTIONAL,
                     -- Any restriction ID tables which have  
                     -- established for these map entries 
   regional          SEQUENCE (SIZE(1..4)) OF 
                     RegionalExtension {{Reg-MapData}} OPTIONAL,
   
   -- NOTE:
   -- Other map data will be added here as it is defined
   -- Examples of the type of content to be added include
   -- curve warnings, construction routes, etc.
   ...
   }


ConnectingLane ::= SEQUENCE {
   lane      LaneID,   -- Index of the connecting lane
   maneuver  AllowedManeuvers OPTIONAL
                       -- The Maneuver between 
                       -- the enclosing lane and this lane
                       -- at the stop line to connect them
   }


Connection ::= SEQUENCE {
   -- The subject lane connecting to this lane is:
   connectingLane     ConnectingLane, 
                      -- The index of the connecting lane and also
                      -- the maneuver from the current lane to it
   remoteIntersection IntersectionReferenceID OPTIONAL,  
                      -- This entry is only used when the 
                      -- indicated connecting lane belongs 
                      -- to another intersection layout. This 
                      -- provides a means to create meshes of lanes
   
   -- SPAT mapping details at the stop line are:
   signalGroup        SignalGroupID OPTIONAL,    
                      -- The matching signal group send by 
                      -- the SPAT message for this lane/maneuver.
                      -- Shall be present unless the connectingLane 
                      -- has no signal group (is un-signalized)
   userClass          RestrictionClassID OPTIONAL, 
                      -- The Restriction Class of users this applies to
                      -- The use of some lane/maneuver and SignalGroupID 
                      -- pairings are restricted to selected users.
                      -- When absent, the SignalGroupID applies to all
   
   -- Movement assist details are given by:
   connectionID       LaneConnectionID OPTIONAL
                      -- An optional connection index used to 
                      -- relate this lane connection to any dynamic 
                      -- clearance data in the SPAT. Note that
                      -- the index may be shared with other 
                      -- connections if the clearance data is common
   }


ConnectsToList ::= SEQUENCE (SIZE(1..16)) OF Connection


DataParameters ::= SEQUENCE {
   processMethod     IA5String(SIZE(1..255)) OPTIONAL, 
   processAgency     IA5String(SIZE(1..255)) OPTIONAL, 
   lastCheckedDate   IA5String(SIZE(1..255)) OPTIONAL, 
   geoidUsed         IA5String(SIZE(1..255)) OPTIONAL, 
   ...  
   }


GenericLane ::= SEQUENCE { 
   laneID           LaneID, 
                    -- The unique ID number assigned 
                    -- to this lane object
   name             DescriptiveName OPTIONAL,        
                    -- often for debug use only 
                    -- but at times used to name ped crossings
   ingressApproach  ApproachID OPTIONAL, -- inbound
   egressApproach   ApproachID OPTIONAL, -- outbound
                    -- Approach IDs to which this lane belongs
   laneAttributes   LaneAttributes, 
                    -- All Attribute information about 
                    -- the basic selected lane type
                    -- Directions of use, Geometric co-sharing
                    -- and Type Specific Attributes
                    -- These Attributes are 'lane - global' that is,
                    -- they are true for the entire length of the lane
   maneuvers        AllowedManeuvers OPTIONAL,
                    -- the permitted maneuvers for this lane
   nodeList         NodeListXY,
                    -- Lane spatial path information as well as
                    -- various Attribute information along the node path  
                    -- Attributes found here are more general and may
                    -- come and go over the length of the lane.
   connectsTo       ConnectsToList OPTIONAL, 
                    -- a list of other lanes and their signal group IDs
                    -- each connecting lane and its signal group ID
                    -- is given, therefore this element provides the
                    -- information formerly in "signalGroups" in prior
                    -- editions.
   overlays         OverlayLaneList OPTIONAL, 
                    -- A list of any lanes which have spatial paths that
                    -- overlay (run on top of, and not simply cross) 
                    -- the path of this lane when used. An overlay
                    -- for one lane can be applied to parallel lanes
                    -- without repeating OverlayLaneList for each GenericLane
                    -- entry.
   regional  SEQUENCE (SIZE(1..4)) OF 
             RegionalExtension {{Reg-GenericLane}} OPTIONAL,
   ...
   }


IntersectionGeometry ::= SEQUENCE {
   name        DescriptiveName OPTIONAL, 
                            -- For debug use only
   id          IntersectionReferenceID,  
                            -- A globally unique value set, 
                            -- consisting of a regionID and 
                            -- intersection ID assignment
   revision    MsgCount,    

   -- Required default values about lane descriptions follow
   refPoint    Position3D,  -- The reference from which subsequent 
                            -- data points are offset until a new
                            -- point is used. 
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given 
                            -- See Section 11 for converting and 
                            -- translating speed expressed in mph 
                            -- into units of m/s
   -- Complete details regarding each lane type in this intersection
   laneSet     LaneList,    -- Data about one or more lanes
                            -- (all lane data is found here)
   
   -- Data describing how to use and request preemption and
   -- priority services from this intersection (if supported)
   -- NOTE Additonal data may be added in the next release of the 
   -- standard at this point to handle this concept
   preemptPriorityData PreemptPriorityList OPTIONAL, 
                           -- data about one or more regional
                           -- preempt or priority zones 
   
   regional     SEQUENCE (SIZE(1..4)) OF 
                RegionalExtension {{Reg-IntersectionGeometry}} OPTIONAL,
   ...,
   roadAuthorityID			RoadAuthorityID		OPTIONAL
   -- Mandatory if roadRegulatorID is set to 0   
   }


IntersectionGeometryList ::= SEQUENCE (SIZE(1..32)) OF IntersectionGeometry


LaneAttributes ::= SEQUENCE {
   directionalUse  LaneDirection,      -- directions of lane use
   sharedWith      LaneSharing,        -- co-users of the lane path
   laneType        LaneTypeAttributes, -- specific lane type data
   regional        RegionalExtension {{Reg-LaneAttributes}} OPTIONAL
   }


LaneList ::= SEQUENCE (SIZE(1..255)) OF GenericLane


LaneTypeAttributes ::= CHOICE {
   vehicle        LaneAttributes-Vehicle,        -- motor vehicle lanes
   crosswalk      LaneAttributes-Crosswalk,      -- pedestrian crosswalks
   bikeLane       LaneAttributes-Bike,           -- bike lanes
   sidewalk       LaneAttributes-Sidewalk,       -- pedestrian sidewalk paths
   median         LaneAttributes-Barrier,        -- medians & channelization
   striping       LaneAttributes-Striping,       -- roadway markings
   trackedVehicle LaneAttributes-TrackedVehicle, -- trains and trolleys
   parking        LaneAttributes-Parking,        -- parking and stopping lanes
   ...
   } 


OverlayLaneList ::= SEQUENCE (SIZE(1..5)) OF LaneID
   -- The unique ID numbers for any lane object which have
   -- spatial paths that overlay (run on top of, and not
   -- simply cross with) the current lane.
   -- Such as a train path that overlays a motor vehicle
   -- lane object for a roadway segment.


PreemptPriorityList ::= SEQUENCE (SIZE(1..32)) OF SignalControlZone

SignalControlZone ::=  SEQUENCE {
  zone  RegionalExtension {{Reg-SignalControlZone}},
  ...
  }


RestrictionClassAssignment ::= SEQUENCE {
   id       RestrictionClassID,
            -- the unique value (within an intersection or local region)
            -- that is assigned to this group of users
   users    RestrictionUserTypeList 
            -- The list of user types/classes 
            -- to which this restriction ID applies
   }


RestrictionClassList ::= SEQUENCE (SIZE(1..254)) OF RestrictionClassAssignment


RestrictionUserTypeList ::= SEQUENCE (SIZE(1..16)) OF  RestrictionUserType


RestrictionUserType ::= CHOICE {
   basicType   RestrictionAppliesTo,
               -- a set of the most commonly used types
   regional    SEQUENCE (SIZE(1..4)) OF 
               RegionalExtension {{Reg-RestrictionUserType}}, 
   ...
   }


RoadLaneSetList ::= SEQUENCE (SIZE(1..255)) OF GenericLane


RoadSegmentList ::= SEQUENCE (SIZE(1..32)) OF RoadSegment

   
RoadSegment ::= SEQUENCE {
   name        DescriptiveName OPTIONAL,
   id          RoadSegmentReferenceID,
                           -- a globally unique value for the segment
   revision    MsgCount,    
   -- Required default values about the descriptions to follow
   refPoint    Position3D, -- the reference from which subsequent
                           -- data points are offset until a new
                           -- point is used.
   laneWidth   LaneWidth OPTIONAL,   
                            -- Reference width used by all subsequent 
                            -- lanes unless a new width is given  
   speedLimits SpeedLimitList OPTIONAL, 
                            -- Reference regulatory speed limits
                            -- used by all subsequent 
                            -- lanes unless a new speed is given   
                            -- See Section 11 for converting and  
                            -- translating speed expressed in mph 
                            -- into units of m/s
                         
   -- Data describing disruptions in the RoadSegment
   -- such as work zones etc will be added here;
   -- in the US the SAE ITIS codes would be used here
   -- The details regarding each lane type in the RoadSegment
   roadLaneSet RoadLaneSetList,   
  
   regional    SEQUENCE (SIZE(1..4)) OF 
               RegionalExtension {{Reg-RoadSegment}} OPTIONAL,
   ...
   }

AllowedManeuvers ::= BIT STRING {
    -- With bits as defined:
    -- Allowed maneuvers at path end (stop line)
    -- All maneuvers with bits not set are therefore prohibited !
    -- A value of zero shall be used for unknown, indicating no Maneuver
    maneuverStraightAllowed      (0), 
                                  -- a Straight movement is allowed in this lane
    maneuverLeftAllowed          (1),  
                                 -- a Left Turn movement is allowed in this lane
    maneuverRightAllowed         (2), 
                                 -- a Right Turn movement is allowed in this lane
    maneuverUTurnAllowed         (3), 
                                 -- a U turn movement is allowed in this lane
    maneuverLeftTurnOnRedAllowed (4), 
                                 -- a Stop, and then proceed when safe movement 
                                 -- is allowed in this lane  
    maneuverRightTurnOnRedAllowed (5), 
                                 -- a Stop, and then proceed when safe movement 
                                 -- is allowed in this lane  
    maneuverLaneChangeAllowed    (6), 
                                 -- a movement which changes to an outer lane 
                                 -- on the egress side is allowed in this lane
                                 -- (example: left into either outbound lane)
    maneuverNoStoppingAllowed    (7), 
                                 -- the vehicle should not stop at the stop line
                                 -- (example: a flashing green arrow)
    yieldAllwaysRequired         (8), 
                                 -- the allowed movements above are not protected 
                                 -- (example: an permanent yellow condition)
    goWithHalt                   (9), 
                                 -- after making a full stop, may proceed
    caution                      (10), 
                                 -- proceed past stop line with caution
    reserved1                    (11)
                                 -- used to align to 12 Bit Field
   
   } (SIZE(12))  
 
LaneAttributes-Barrier ::= BIT STRING {
   -- With bits as defined:
   median-RevocableLane     (0),
                            -- this lane may be activated or not based
                            -- on the current SPAT message contents
                            -- if not asserted, the lane is ALWAYS present
   median                   (1),
   whiteLineHashing         (2),
   stripedLines             (3),
   doubleStripedLines       (4),
   trafficCones             (5),
   constructionBarrier      (6),
   trafficChannels          (7),
   lowCurbs                 (8),
   highCurbs                (9)
   -- Bits 10~15 reserved and set to zero
   } (SIZE (16))

LaneAttributes-Bike ::= BIT STRING {
   -- With bits as defined:
   bikeRevocableLane       (0),
                           -- this lane may be activated or not based
                           -- on the current SPAT message contents
                           -- if not asserted, the lane is ALWAYS present
   pedestrianUseAllowed    (1),
                           -- The path allows pedestrian traffic, 
                           -- if not set, this mode is prohibited
   isBikeFlyOverLane       (2),
                           -- path of lane is not at grade
   fixedCycleTime          (3),
                           -- the phases use preset times
                           -- i.e., there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entries
                           -- in the Connect follow this same pattern in pairs.
   isolatedByBarrier       (5),
   unsignalizedSegmentsPresent  (6)
                           -- The lane path consists of one of more segments
                           -- which are not part of a signal group ID

   -- Bits 7~15 reserved and set to zero
   } (SIZE (16))

LaneAttributes-Crosswalk ::= BIT STRING { 
   -- With bits as defined:
   -- MUTCD provides no suitable "types" to use here
   crosswalkRevocableLane  (0),
                           -- this lane may be activated or not based
                           -- on the current SPAT message contents
                           -- if not asserted, the lane is ALWAYS present
   bicyleUseAllowed        (1),
                           -- The path allows bicycle traffic, 
                           -- if not set, this mode is prohibited
   isXwalkFlyOverLane      (2),
                           -- path of lane is not at grade
   fixedCycleTime          (3),
                           -- ped walk phases use preset times
                           -- i.e., there is not a 'push to cross' button
   biDirectionalCycleTimes (4),
                           -- ped walk phases use different SignalGroupID
                           -- for each direction. The first SignalGroupID
                           -- in the first Connection represents 'inbound'
                           -- flow (the direction of travel towards the first 
                           -- node point) while second SignalGroupID in the 
                           -- next Connection entry represents the 'outbound'
                           -- flow. And use of RestrictionClassID entries
                           -- in the Connect follow this same pattern in pairs.
   hasPushToWalkButton     (5),
                           -- Has a demand input
   audioSupport            (6),
                           -- audio crossing cues present
   rfSignalRequestPresent  (7),
                           -- Supports RF push to walk technologies
   unsignalizedSegmentsPresent  (8)
                           -- The lane path consists of one of more segments
                           -- which are not part of a signal group ID
   -- Bits 9~15 reserved and set to zero
   } (SIZE (16))

LaneAttributes-Parking ::= BIT STRING { 
    -- With bits as defined:
    -- Parking use details, note that detailed restrictions such as 
    -- allowed hours are sent by way of ITIS codes in the TIM message
    parkingRevocableLane         (0),
                                 -- this lane may be activated or not based
                                 -- on the current SPAT message contents
                                 -- if not asserted, the lane is ALWAYS present
    parallelParkingInUse         (1),
    headInParkingInUse           (2),
    doNotParkZone                (3),
                                 -- used to denote fire hydrants as well as
                                 -- short disruptions in a parking zone
    parkingForBusUse             (4),
    parkingForTaxiUse            (5),
    noPublicParkingUse           (6)
                                 -- private parking, as in front of
                                 -- private property
   -- Bits 7~15 reserved and set to zero
   } (SIZE (16))

LaneAttributes-Sidewalk ::= BIT STRING { 
   -- With bits as defined:
   sidewalk-RevocableLane  (0),
                           -- this lane may be activated or not based
                           -- on the current SPAT message contents
                           -- if not asserted, the lane is ALWAYS present
   bicyleUseAllowed        (1),
                           -- The path allows bicycle traffic, 
                           -- if not set, this mode is prohibited
   isSidewalkFlyOverLane   (2),
                           -- path of lane is not at grade
   walkBikes               (3)
                           -- bike traffic must dismount and walk
   -- Bits 4~15 reserved and set to zero
   } (SIZE (16))


LaneAttributes-Striping ::= BIT STRING { 
   -- With bits as defined:
    stripeToConnectingLanesRevocableLane      (0),
       -- this lane may be activated or not activated based
       -- on the current SPAT message contents
       -- if not asserted, the lane is ALWAYS present
    stripeDrawOnLeft                          (1),
    stripeDrawOnRight                         (2),
        -- which side of lane to mark
    stripeToConnectingLanesLeft               (3),
    stripeToConnectingLanesRight              (4),
    stripeToConnectingLanesAhead              (5)
        -- the stripe type should be
        -- presented to the user visually
        -- to reflect stripes in the 
        -- intersection for the type of
        -- movement indicated
   -- Bits 6~15 reserved and set to zero
   } (SIZE (16))


LaneAttributes-TrackedVehicle ::= BIT STRING { 
   -- With bits as defined:
   spec-RevocableLane         (0),
                               -- this lane may be activated or not based
                               -- on the current SPAT message contents
                               -- if not asserted, the lane is ALWAYS present
   spec-commuterRailRoadTrack (1), 
   spec-lightRailRoadTrack    (2),
   spec-heavyRailRoadTrack    (3),
   spec-otherRailType         (4)
   -- Bits 5~15 reserved and set to zero
   } (SIZE (16))


LaneAttributes-Vehicle ::= BIT STRING {  
   -- With bits as defined:
   isVehicleRevocableLane       (0),
                                 -- this lane may be activated or not based
                                 -- on the current SPAT message contents
                                 -- if not asserted, the lane is ALWAYS present
   isVehicleFlyOverLane         (1),
                                 -- path of lane is not at grade
   hovLaneUseOnly               (2),
   restrictedToBusUse           (3),
   restrictedToTaxiUse          (4),
   restrictedFromPublicUse      (5),
   hasIRbeaconCoverage          (6),
   permissionOnRequest          (7) -- e.g., to inform about a lane for e-cars

   } (SIZE (8,...))

LaneDirection ::= BIT STRING {
   -- With bits as defined:
   -- Allowed directions of travel in the lane object
   -- All lanes are described from the stop line outwards
   ingressPath     (0), 
                   -- travel from rear of path to front 
                   -- is allowed
   egressPath      (1)
                   -- travel from front of path to rear 
                   -- is allowed
   -- Notes:  No Travel, i.e., the lane object type does not support
   --         travel (medians, curbs, etc.) is indicated by not 
   --         asserting any bit value
   --         Bi-Directional Travel (such as a ped crosswalk) is 
   --         indicated by asserting both of the bits
   } (SIZE (2))

LaneSharing ::= BIT STRING {
    -- With bits as defined:
    overlappingLaneDescriptionProvided  (0),
    -- Assert when another lane object is present to describe the
    -- path of the overlapping shared lane
    -- this construct is not used for lane objects which simply cross
    multipleLanesTreatedAsOneLane       (1),
    -- Assert if the lane object path and width details represents
    -- multiple lanes within it that are not further described

    -- Various modes and type of traffic that may share this lane:
    otherNonMotorizedTrafficTypes       (2), -- horse drawn etc.
    individualMotorizedVehicleTraffic   (3),
    busVehicleTraffic                   (4),  
    taxiVehicleTraffic                  (5),
    pedestriansTraffic                  (6),
    cyclistVehicleTraffic               (7),
    trackedVehicleTraffic               (8),
    reserved                            (9)
    } (SIZE (10))
    -- All zeros would indicate 'not shared' and 'not overlapping'

LayerID ::= INTEGER (0..100)

LayerType ::= ENUMERATED {
     none, 
     mixedContent, -- two or more of the below types
     generalMapData, 
     intersectionData, 
     curveData, 
     roadwaySectionData, 
     parkingAreaData, 
     sharedLaneData,
     ... 
     } 

RestrictionAppliesTo ::= ENUMERATED {
    none,              -- applies to nothing
    equippedTransit,   -- buses etc.
    equippedTaxis,
    equippedOther,     -- other vehicle types with
                       -- necessary signal phase state
                       -- reception equipment
    emissionCompliant, -- regional variants with more
                       -- definitive items also exist
    equippedBicycle,
    weightCompliant,
    heightCompliant,
    -- Items dealing with traveler needs serviced by the infrastructure
    -- These end users (which are not vehicles) are presumed to be suitably equipped
    pedestrians,
    slowMovingPersons,
    wheelchairUsers,
    visualDisabilities,
    audioDisabilities,  -- hearing
    otherUnknownDisabilities,
    ...
    }
END
