--
-- Terms and Conditions and User License Agreement - Download and Use of ASN File
-- 
-- Copyright: Each ASN File contained herein ("File") is copyrighted and all
-- rights, title, and interest in and to each File are owned by SAE. The 
-- license contained herein applies to each File and each reference in this license
-- to "the File" or "this File" shall be construed to include each and any ASN File
-- contained herein. No rights therein are granted except as set forth in this
-- License. Any copying, transmission, modification or reproduction of the File or
-- the copyrighted material within it, in part or in whole, except as herein
-- permitted is cause for revocation of this License.
-- 
-- License: SAE International ("SAE") hereby grants to you, as an individual or as
-- a single corporate entity, a limited nonexclusive, nontransferable right to
-- download this File in an electronic format for your individual use or use by
-- a single corporate entity on one computer. One hard copy of the File can also
-- be printed for individual use or use by a single corporate entity. SAE also
-- hereby grants to you the nonexclusive, nontransferable right to use this File
-- and create derivative works using this File for your own or your own corporate
-- entity's research purposes and in the design, creation, manufacture, distribution,
-- and use of your own products. For purposes of clarification, derivative works
-- permitted under this license include derivative works or source code that do not
-- include or incorporate this File. The derivative work may use the File to create
-- source code and corresponding software programs.  Notwithstanding the foregoing,
-- you agree that you must obtain a license from SAE to create any derivative works
-- which incorporate this File or its contents.
--
-- SAE also hereby grants to you the nonexclusive, nontransferable right to copy,
-- reproduce, distribute to others the derivative works from the use of the content
-- of this File or portions thereof in or as part of your company's products.
-- You must only license, and not otherwise sell or transfer, the products, software,
-- and software documentation that incorporates content from this File, and you must
-- prohibit any licensees or others from transferring, copying, or extracting the
-- contents of this File thereof for use in their own or others' software or products.
--
-- Other than as expressly permitted herein, this File may not be copied in whole in
-- any form for distribution to other users or other computers, including without
-- limitation to other individuals or users within your own corporate entity or
-- outside your corporate entity.  This license prohibits the end user from posting
-- or distributing content via any public forum or as open access content.  If other
-- individuals in or outside your corporate entity or different cooperate entities,
-- whether related or not to your corporate entity, wish to download or copy this
-- File, they must purchase a separate individual license to do so. 
-- 
-- This File is licensed "AS IS" to you and you do hereby hold SAE harmless from your
-- use of the File or the creative or use of derivative works thereof, and you agree
-- to indemnify SAE from any and all claims or damages caused by your use,
-- reproduction, distribution to others, or application of this File or any
-- derivative works therefrom.  SAE may amend the terms of and conditions of
-- this License or cancel this License at any time in its sole discretion and
-- for any reason by reasonable notice, including without limitation by posting
-- revised terms on its website.  
--
-- General: Files that have been successfully downloaded cannot be returned for
-- refund or credit. This Agreement is the complete and exclusive statement of the
-- agreement between you and SAE and supersedes any and all prior agreements or
-- understandings, either written or oral, concerning the subject of this Agreement.
-- Any modifications must be in writing and signed by the parties.
-- 
-- Notice to Resellers: Authorized resellers of SAE Files may download this File on
-- behalf of their customers and forward it directly, unopened, to their customers
-- provided their customers agree to abide by the terms of this License. Resellers
-- may not otherwise copy, transmit, modify or reproduce this File.
-- 
-- This license will remain in effect for the life of the standards associated with
-- the File unless otherwise amended or cancelled by SAE in its sole discretion.
-- In the event that the associated standard is cancelled or recalled due to interest
-- of public safety, the aforementioned License will be rescinded as well. This 
-- License shall terminate upon violation of any of its terms.
--
-- (C)2024 SAE International.  All rights reserved.  SAE International retains the
-- right to entertain or negotiate requests for customized distribution agreements
-- for multi-user or corporate use and / or distribution. Requests should be submitted
-- to customerservice@sae.org.
--

--
-- Use of this module defined in SAE J2735 
-- Latest document release for this module is Nov 2022
-- Filename: J2735-ProbeVehicleData-2024-rel-v1.1.asn 
--

ProbeVehicleData
{joint-iso-itu-t (2) country (16) us (840) organization (1) sae (114566)
v2x-communications (1) technical-committees (1) v2x-core (5) technical-reports (1)
j2735 (2735) part-0 (0) asn1-module (1) probeVehicleData (15) 
version-1 (1) version-minor-1 (1)}

DEFINITIONS AUTOMATIC TAGS ::=
BEGIN

IMPORTS 
	Reg-ProbeVehicleData
		FROM REGION {joint-iso-itu-t (2) country (16) us (840) organization (1) sae (114566)
		v2x-communications (1) technical-committees (1) v2x-core (5) technical-reports (1)
		j2735 (2735) part-0 (0) asn1-module (1) region (2) 
		version-1 (1) version-minor-1 (1)} WITH SUCCESSORS
	EssPrecipYesNo, 
	EssPrecipRate, 
	EssPrecipSituation, 
	EssSolarRadiation, 
	EssMobileFriction
		FROM NTCIP {joint-iso-itu-t (2) country (16) us (840) organization (1) sae (114566)
		v2x-communications (1) technical-committees (1) v2x-core (5) technical-reports (1)
		j2735 (2735) part-0 (0) asn1-module (1) ntcip (5) 
		version-1 (1) version-minor-1 (1)} WITH SUCCESSORS
	VehicleGroupAffected, 
	ResponderGroupAffected, 
	IncidentResponseEquipment
		FROM ITIS {joint-iso-itu-t (2) country (16) us (840) organization (1) sae (114566)
		v2x-communications (1) technical-committees (1) v2x-core (5) technical-reports (1)
		j2735 (2735) part-0 (0) asn1-module (1) itis (6) 
		version-1 (1) version-minor-1 (1)} WITH SUCCESSORS
	MinuteOfTheYear, 
	FullPositionVector, 
	VehicleClassification, 
	RegionalExtension, 
	SpeedandHeadingandThrottleConfidence, 
	TimeConfidence, 
	PositionConfidenceSet, 
	HeadingConfidence, 
	ThrottleConfidence, 
	TrailerWeight, 
	VehicleSafetyExtensions, 
	DescriptiveName, 
	VehicleID, 
	VehicleType, 
	ExteriorLights, 
	LightbarInUse, 
	WiperSet, 
	BrakeSystemStatus, 
	CoefficientOfFriction, 
	AmbientAirTemperature, 
	AmbientAirPressure, 
	SteeringWheelAngle, 
	AccelerationSet4Way, 
	VerticalAccelerationThreshold, 
	ObstacleDistance, 
	Angle, 
	DDateTime, 
	SpeedConfidence, 
	VehicleHeight, 
	BumperHeights, 
	VehicleMass, 
	GNSSstatus
		FROM Common {joint-iso-itu-t (2) country (16) us (840) organization (1) sae (114566)
		v2x-communications (1) technical-committees (1) v2x-core (5) technical-reports (1)
		j2735 (2735) part-0 (0) asn1-module (1) common (38) 
		version-1 (1) version-minor-1 (1)} WITH SUCCESSORS;





ProbeVehicleData ::= SEQUENCE {
   timeStamp       MinuteOfTheYear OPTIONAL,
   segNum          ProbeSegmentNumber OPTIONAL,   
                                         -- a short term Ident value
                                         -- not used when ident is used
   probeID         VehicleIdent OPTIONAL, 
                                         -- identity data for selected 
                                         -- types of vehicles    
   startVector     FullPositionVector,   -- the space and time of 
                                         -- transmission to the RSU
   vehicleType     VehicleClassification, -- type of vehicle, 
   snapshots       SEQUENCE (SIZE(1..32)) OF Snapshot,               
                                         -- a seq of name-value pairs 
                                         -- along with the space and time 
                                         -- of the first measurement set
   regional        SEQUENCE (SIZE(1..4)) OF 
                   RegionalExtension {{Reg-ProbeVehicleData}} OPTIONAL,
   ...
   }


AccelSteerYawRateConfidence ::= SEQUENCE {
   yawRate             YawRateConfidence, 
   acceleration        AccelerationConfidence, 
   steeringWheelAngle  SteeringWheelAngleConfidence 
   }


ConfidenceSet ::= SEQUENCE {
   accelConfidence      AccelSteerYawRateConfidence OPTIONAL,    
   speedConfidence      SpeedandHeadingandThrottleConfidence OPTIONAL,      
   timeConfidence       TimeConfidence OPTIONAL,           
   posConfidence        PositionConfidenceSet OPTIONAL,           
   steerConfidence      SteeringWheelAngleConfidence OPTIONAL,
   headingConfidence    HeadingConfidence OPTIONAL,
   throttleConfidence   ThrottleConfidence OPTIONAL,
   ...  
   }


J1939data ::= SEQUENCE {
   -- Tire conditions by tire
   tires                    TireDataList              OPTIONAL,
   -- Vehicle Weights by axle
   axles                    AxleWeightList            OPTIONAL,      
   trailerWeight            TrailerWeight             OPTIONAL,     
   cargoWeight              CargoWeight               OPTIONAL, 
   steeringAxleTemperature  SteeringAxleTemperature   OPTIONAL, 
   driveAxleLocation        DriveAxleLocation         OPTIONAL, 
   driveAxleLiftAirPressure DriveAxleLiftAirPressure  OPTIONAL, 
   driveAxleTemperature     DriveAxleTemperature      OPTIONAL, 
   driveAxleLubePressure    DriveAxleLubePressure     OPTIONAL, 
   steeringAxleLubePressure SteeringAxleLubePressure  OPTIONAL, 
   ...
   }   


TireDataList ::= SEQUENCE (SIZE(1..16)) OF TireData 


TireData ::= SEQUENCE {
      location              TireLocation              OPTIONAL, 
      pressure              TirePressure              OPTIONAL, 
      temp                  TireTemp                  OPTIONAL, 
      wheelSensorStatus     WheelSensorStatus         OPTIONAL, 
      wheelEndElectFault    WheelEndElectFault        OPTIONAL, 
      leakageRate           TireLeakageRate           OPTIONAL, 
      detection             TirePressureThresholdDetection OPTIONAL, 
      ...
      }

AxleWeightList ::= SEQUENCE (SIZE(1..16)) OF AxleWeightSet

AxleWeightSet ::= SEQUENCE {
      location              AxleLocation              OPTIONAL, 
      weight                AxleWeight                OPTIONAL, 
      ...
      }


Snapshot ::= SEQUENCE {
   thePosition  FullPositionVector,          
                -- data of the position and speed, 
   safetyExt    VehicleSafetyExtensions OPTIONAL, 
   dataSet      VehicleStatus           OPTIONAL,  
                -- a sequence of data frames
                -- which encodes the data
   ...  
   }


VehicleIdent ::= SEQUENCE {
   name           DescriptiveName OPTIONAL,
                  -- a human readable name for debugging use
   vin            VINstring OPTIONAL,
                  -- vehicle VIN value
   ownerCode      IA5String(SIZE(1..32)) OPTIONAL,
                  -- vehicle owner code 
   id             VehicleID OPTIONAL, 
                  -- same value used in the BSM
      
   vehicleType    VehicleType  OPTIONAL, 
   vehicleClass   CHOICE {
                     vGroup   VehicleGroupAffected,
                     rGroup   ResponderGroupAffected,
                     rEquip   IncidentResponseEquipment  
                  } OPTIONAL, 
   ...  
   }


VehicleStatus ::= SEQUENCE { 
   lights          ExteriorLights OPTIONAL,                 -- Exterior Lights
   lightBar        LightbarInUse  OPTIONAL,                 -- PS Lights
   
   wipers          WiperSet OPTIONAL,                      -- Wipers
   
   brakeStatus     BrakeSystemStatus OPTIONAL, 
                                                            -- Braking Data
   brakePressure   BrakeAppliedPressure  OPTIONAL,          -- Braking Pressure
   roadFriction    CoefficientOfFriction OPTIONAL,          -- Roadway Friction 
   
      
   sunData         SunSensor             OPTIONAL,          -- Sun Sensor        
   rainData        RainSensor            OPTIONAL,          -- Rain Sensor        
   airTemp         AmbientAirTemperature OPTIONAL,          -- Air Temperature    
   airPres         AmbientAirPressure    OPTIONAL,          -- Air Pressure
   
   steering   SEQUENCE {
         angle      SteeringWheelAngle,   
         confidence SteeringWheelAngleConfidence   OPTIONAL,    
         rate       SteeringWheelAngleRateOfChange OPTIONAL,   
         wheels     DrivingWheelAngle              OPTIONAL
         } OPTIONAL,                               -- steering data
   
   accelSets  SEQUENCE {
         accel4way       AccelerationSet4Way           OPTIONAL, 
         vertAccelThres  VerticalAccelerationThreshold OPTIONAL, 
                                                   -- Wheel which has 
                                                   -- exceeded acceleration point
         yawRateCon      YawRateConfidence             OPTIONAL, 
                                                   -- Yaw Rate Confidence
         hozAccelCon     AccelerationConfidence        OPTIONAL,     
                                                   -- Acceleration Confidence 
         confidenceSet   ConfidenceSet                 OPTIONAL
                                                   -- general ConfidenceSet 
         } OPTIONAL, 
                                  
   
   object     SEQUENCE {
         obDist          ObstacleDistance,          -- Obstacle Distance        
         obDirect        Angle,                     -- Obstacle Direction        
         dateTime        DDateTime                  -- time detected
         } OPTIONAL,                                -- detected Obstacle data
   
   
   
   fullPos         FullPositionVector OPTIONAL,     -- complete set of time and
                                                    -- position, speed, heading
   throttlePos     ThrottlePosition OPTIONAL,
   speedHeadC      SpeedandHeadingandThrottleConfidence OPTIONAL,    
   speedC          SpeedConfidence OPTIONAL,
   
   vehicleData   SEQUENCE {    
         height        VehicleHeight,
         bumpers       BumperHeights,
         mass          VehicleMass,
         trailerWeight TrailerWeight,
         type          VehicleType 
         -- values for width and length are sent in BSM part I as well. 
         } OPTIONAL,                            -- vehicle data
   
   vehicleIdent   VehicleIdent OPTIONAL,        -- common vehicle identity data
 
   j1939data      J1939data OPTIONAL,           -- Various SAE J1938 data items
     
   weatherReport SEQUENCE {    
         isRaining        EssPrecipYesNo,
         rainRate         EssPrecipRate       OPTIONAL,
         precipSituation  EssPrecipSituation  OPTIONAL,
         solarRadiation   EssSolarRadiation   OPTIONAL,
         friction         EssMobileFriction   OPTIONAL
         } OPTIONAL,                                        -- local weather data
      
   gnssStatus      GNSSstatus          OPTIONAL,              -- vehicle's GPS
 
   ...          
   }

AccelerationConfidence ::= ENUMERATED {
   unavailable  (0), -- Not Equipped or data is unavailable
   accl-100-00  (1), -- 100  meters / second squared
   accl-010-00  (2), -- 10   meters / second squared
   accl-005-00  (3), -- 5    meters / second squared
   accl-001-00  (4), -- 1    meters / second squared
   accl-000-10  (5), -- 0.1  meters / second squared
   accl-000-05  (6), -- 0.05 meters / second squared
   accl-000-01  (7)  -- 0.01 meters / second squared
   } -- Encoded as a 3 bit value  

BrakeAppliedPressure ::= ENUMERATED {
   unavailable  (0),  -- B'0000 Not Equipped
                      -- or Brake Pres status is unavailable
   minPressure  (1),  -- B'0001 Minimum Braking Pressure
   bkLvl-2      (2),  -- B'0010
   bkLvl-3      (3),  -- B'0011   
   bkLvl-4      (4),  -- B'0100  
   bkLvl-5      (5),  -- B'0101
   bkLvl-6      (6),  -- B'0110
   bkLvl-7      (7),  -- B'0111
   bkLvl-8      (8),  -- B'1000
   bkLvl-9      (9),  -- B'1001
   bkLvl-10     (10), -- B'1010
   bkLvl-11     (11), -- B'1011
   bkLvl-12     (12), -- B'1100
   bkLvl-13     (13), -- B'1101
   bkLvl-14     (14), -- B'1110
   maxPressure  (15)  -- B'1111 Maximum Braking Pressure
   }  -- Encoded as a 4 bit value

DrivingWheelAngle ::= INTEGER (-128..127) 
   -- LSB units of 0.3333 degrees.  
   -- a range of 42.33 degrees each way

AxleLocation ::= INTEGER (0..255)

AxleWeight ::= INTEGER (0..64255)

CargoWeight ::= INTEGER (0..64255)

DriveAxleLiftAirPressure ::= INTEGER (0..1000)

DriveAxleLocation ::= INTEGER (0..255)

DriveAxleLubePressure ::= INTEGER (0..250)

DriveAxleTemperature ::= INTEGER (-40..210)

SteeringAxleLubePressure ::= INTEGER (0..250)

SteeringAxleTemperature ::= INTEGER (-40..210)

TireLeakageRate ::= INTEGER (0..64255)

TireLocation ::= INTEGER (0..255)

TirePressureThresholdDetection ::= ENUMERATED {
   noData                (0),  -- B'000'
   overPressure          (1),  -- B'001' 
   noWarningPressure     (2),  -- B'010'
   underPressure         (3),  -- B'011'
   extremeUnderPressure  (4),  -- B'100'
   undefined             (5),  -- B'101'
   errorIndicator        (6),  -- B'110'
   notAvailable          (7)   -- B'111'
   }  -- Encoded as a 3 bit value

TirePressure ::= INTEGER (0..250)

TireTemp ::= INTEGER (-8736..55519)

WheelEndElectFault ::= ENUMERATED {
   isOk            (0), -- No fault
   isNotDefined    (1),
   isError         (2),
   isNotSupported  (3)
   }  

WheelSensorStatus ::= ENUMERATED {
   off           (0), 
   on            (1),
   notDefined    (2), 
   notSupported  (3)
   }

ProbeSegmentNumber ::= INTEGER (0..32767)  
   -- value determined by local device 
   -- as per standard

RainSensor ::= ENUMERATED {
     none               (0), 
     lightMist          (1), 
     heavyMist          (2), 
     lightRainOrDrizzle (3),
     rain               (4),
     moderateRain       (5),
     heavyRain          (6),
     heavyDownpour      (7) 
     }

SteeringWheelAngleConfidence ::= ENUMERATED {
   unavailable (0), -- B'00  Not Equipped with Wheel angle
                    -- or Wheel angle status is unavailable
   prec2deg    (1), -- B'01  2 degrees
   prec1deg    (2), -- B'10  1 degree
   prec0-02deg (3)  -- B'11  0.02 degrees
   }

SteeringWheelAngleRateOfChange ::= INTEGER (-127..127) 
   -- LSB is 3 degrees per second

SunSensor ::= INTEGER (0..1000) 
   -- units of watts / m2

ThrottlePosition ::= INTEGER (0..200) -- LSB units are 0.5 percent

VINstring ::= OCTET STRING (SIZE(1..17)) 
   -- A legal VIN or a shorter value 
   -- to provide an ident of the vehicle
   -- If a VIN is sent, then IA5 encoding 
   -- shall be used

YawRateConfidence ::= ENUMERATED {
   unavailable    (0), -- B'000  Not Equipped with yaw rate status
                       -- or yaw rate status is unavailable
   degSec-100-00  (1), -- B'001  100  deg/sec
   degSec-010-00  (2), -- B'010  10   deg/sec
   degSec-005-00  (3), -- B'011  5    deg/sec
   degSec-001-00  (4), -- B'100  1    deg/sec
   degSec-000-10  (5), -- B'101  0.1  deg/sec
   degSec-000-05  (6), -- B'110  0.05 deg/sec
   degSec-000-01  (7)  -- B'111  0.01 deg/sec
   }  
   -- Encoded as a 3 bit value
END
