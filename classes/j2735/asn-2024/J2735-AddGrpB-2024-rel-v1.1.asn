--
-- Terms and Conditions and User License Agreement - Download and Use of ASN File
-- 
-- Copyright: Each ASN File contained herein ("File") is copyrighted and all
-- rights, title, and interest in and to each File are owned by SAE. The 
-- license contained herein applies to each File and each reference in this license
-- to "the File" or "this File" shall be construed to include each and any ASN File
-- contained herein. No rights therein are granted except as set forth in this
-- License. Any copying, transmission, modification or reproduction of the File or
-- the copyrighted material within it, in part or in whole, except as herein
-- permitted is cause for revocation of this License.
-- 
-- License: SAE International ("SAE") hereby grants to you, as an individual or as
-- a single corporate entity, a limited nonexclusive, nontransferable right to
-- download this File in an electronic format for your individual use or use by
-- a single corporate entity on one computer. One hard copy of the File can also
-- be printed for individual use or use by a single corporate entity. SAE also
-- hereby grants to you the nonexclusive, nontransferable right to use this File
-- and create derivative works using this File for your own or your own corporate
-- entity's research purposes and in the design, creation, manufacture, distribution,
-- and use of your own products. For purposes of clarification, derivative works
-- permitted under this license include derivative works or source code that do not
-- include or incorporate this File. The derivative work may use the File to create
-- source code and corresponding software programs.  Notwithstanding the foregoing,
-- you agree that you must obtain a license from SAE to create any derivative works
-- which incorporate this File or its contents.
--
-- SAE also hereby grants to you the nonexclusive, nontransferable right to copy,
-- reproduce, distribute to others the derivative works from the use of the content
-- of this File or portions thereof in or as part of your company's products.
-- You must only license, and not otherwise sell or transfer, the products, software,
-- and software documentation that incorporates content from this File, and you must
-- prohibit any licensees or others from transferring, copying, or extracting the
-- contents of this File thereof for use in their own or others' software or products.
--
-- Other than as expressly permitted herein, this File may not be copied in whole in
-- any form for distribution to other users or other computers, including without
-- limitation to other individuals or users within your own corporate entity or
-- outside your corporate entity.  This license prohibits the end user from posting
-- or distributing content via any public forum or as open access content.  If other
-- individuals in or outside your corporate entity or different cooperate entities,
-- whether related or not to your corporate entity, wish to download or copy this
-- File, they must purchase a separate individual license to do so. 
-- 
-- This File is licensed "AS IS" to you and you do hereby hold SAE harmless from your
-- use of the File or the creative or use of derivative works thereof, and you agree
-- to indemnify SAE from any and all claims or damages caused by your use,
-- reproduction, distribution to others, or application of this File or any
-- derivative works therefrom.  SAE may amend the terms of and conditions of
-- this License or cancel this License at any time in its sole discretion and
-- for any reason by reasonable notice, including without limitation by posting
-- revised terms on its website.  
--
-- General: Files that have been successfully downloaded cannot be returned for
-- refund or credit. This Agreement is the complete and exclusive statement of the
-- agreement between you and SAE and supersedes any and all prior agreements or
-- understandings, either written or oral, concerning the subject of this Agreement.
-- Any modifications must be in writing and signed by the parties.
-- 
-- Notice to Resellers: Authorized resellers of SAE Files may download this File on
-- behalf of their customers and forward it directly, unopened, to their customers
-- provided their customers agree to abide by the terms of this License. Resellers
-- may not otherwise copy, transmit, modify or reproduce this File.
-- 
-- This license will remain in effect for the life of the standards associated with
-- the File unless otherwise amended or cancelled by SAE in its sole discretion.
-- In the event that the associated standard is cancelled or recalled due to interest
-- of public safety, the aforementioned License will be rescinded as well. This 
-- License shall terminate upon violation of any of its terms.
--
-- (C)2024 SAE International.  All rights reserved.  SAE International retains the
-- right to entertain or negotiate requests for customized distribution agreements
-- for multi-user or corporate use and / or distribution. Requests should be submitted
-- to customerservice@sae.org.
--

--
-- Use of this module defined in SAE J2735 
-- Latest document release for this module is Nov 2022
-- Filename: J2735-AddGrpB-2024-rel-v1.1.asn 
--

AddGrpB
{joint-iso-itu-t (2) country (16) us (840) organization (1) sae (114566)
v2x-communications (1) technical-committees (1) v2x-core (5) technical-reports (1)
j2735 (2735) part-0 (0) asn1-module (1) addgrpb (4) version-1 (1) version-minor-1 (1)}

DEFINITIONS AUTOMATIC TAGS ::=
BEGIN

IMPORTS 
	TimeIntervalConfidence
		FROM SPAT {joint-iso-itu-t (2) country (16) us (840) organization (1) sae (114566)
		v2x-communications (1) technical-committees (1) v2x-core (5) technical-reports (1)
		j2735 (2735) part-0 (0) asn1-module (1) signalPhaseAndTimingMessage (9) 
		version-1 (1) version-minor-1 (1)} WITH SUCCESSORS; 
 
Angle ::= INTEGER (0..239)
   -- Unsigned units of 1.5 degree, in 1 octet
   -- the true north is 0, positive is clockwise
   -- the values 240 to 254 shall not be sent
   -- the value 255 (0xFF) indicates an invalid value

Day ::= INTEGER (0..255) 
   -- BCD coding of Day of Month, in 1 octet
   -- values with nibble values between 1010 and 1111 shall not be sent
   -- except that the value xxx (0xFF shall indicate an invalid value

DayOfWeek ::= ENUMERATED {
    unknown   (0),
    monday    (1),
    tuesday   (2),
    wednesday (3),
    thursday  (4),
    friday    (5),
    saturday  (6),
    sunday    (7)
    }
   -- Encoding as per above, in 3 bits
   -- the value 0x00 shall indicate an invalid value

DegreesLat ::= INTEGER (-90..90)
   -- Signed units of degrees, in 1 octets
   -- the values  +91 to +126 shall not be sent
   -- the values -128 to  -91 shall not be sent
   -- the value 127 (0x7F) shall indicate an invalid value

DegreesLong ::= INTEGER (-180..180) 
   -- Signed units of degrees, in 2 octets
   -- the values +181 to +32766 shall not be sent
   -- the values -181 to -32768 shall not be sent
   -- the value 32767 (0x7FFF shall indicate an invalid value

Elevation ::= INTEGER (-32768..32767)  
  -- Signed units of 0.1m (10cm), in 2 octets
  -- the value 32767 (0x7FFF) shall indicate an invalid value

Holiday ::= ENUMERATED {
    weekday  (0),
    holiday  (1)
    }
   -- Encoding as per above, in 1 bit

Hour ::= INTEGER (0..255) 
   -- BCD coding of Hour of a Day, in 1 octet
   -- values above upper nibble 0010 and lower nibble 0100 shall not be sent
   -- values with lower nibble values between 1010 and 1111 shall not be sent
   -- except that the value 255 (0xFF) shall indicate an invalid value

LatitudeDMS ::= INTEGER (-32400000.. 32400000) 
   -- Signed units of 0.01 seconds of a minute of a degree of Latitude
   -- Providing a range of plus-minus 90 degrees
   -- in a 4 octet value when implicit or in BER forms
   -- the value 0x7FFF FFFF shall indicate an invalid value

LongitudeDMS ::= INTEGER (-64800000.. 64800000) 
   -- Signed units of 0.01 seconds of a minute of a degree of Longitude
   -- Providing a range of plus-minus 180 degrees
   -- in a 4 octet value when implicit or in BER forms
   -- the value 0x7FFF FFFF shall indicate an invalid value

MaxTimetoChange ::= INTEGER (0..2402)
   -- Unsigned units of 0.1 seconds, in 2 octets
   -- the value 2401 shall indicate 'forever'
   -- the values 2402 to 65534 shall not be sent
   -- the value 65535 (0xFFFF) shall indicate an invalid value

MinTimetoChange ::= INTEGER (0..2402)
   -- Unsigned units of 0.1 seconds, in 2 octets
   -- the value 2401 shall indicate 'forever'
   -- the values 2402 to 32766 shall not be sent
   -- the value 32767(0x7FFF) shall indicate an invalid value
   -- Note that:
   -- The MSB is used as a flag and set to one to
   -- indicate that the value does not count down.
   -- Under this condition the movement phase may end
   -- immediately if certain condition are meet.

Minute ::= INTEGER (0..255) 
   -- BCD coding of Minute of an Hour, in 1 octet 
   -- values above a combined BCD value of 59 (>59)
   -- (i.e., 0110 0000) shall not be sent
   -- except that value 255 (0xFF) shall indicate an invalid value

MinutesAngle ::= INTEGER (0..59)   
   -- Unsigned units of minutes of an angle, in 1 octet 
   -- values above 59 shall not be sent
   -- except that value 255 (0xFF) shall indicate an invalid value

Month ::= INTEGER (1..255) 
   -- BCD coding of Month of a year, in 1 octet
   -- values above a combined BCD value of 12 (>12)
   -- (i.e., 0001 0011) shall not be sent
   -- except that value 255 (0xFF) shall indicate an invalid value

MsgCount ::= INTEGER (0..255)
   -- a count value which is incremented with each use
   -- the next value after 255 shall be one
   -- value 0 (0x00) shall indicate that MsgCount is not available

Second ::= INTEGER (0..60) 
   -- BCD coding of a second of time, in 1 octet 
   -- values above a combined BCD value of 60
   -- (i.e., 0110 0000) shall not be sent
   -- except that value 255 (0xFF) shall indicate an invalid value

SecondsAngle ::= INTEGER (0..5999)  
   -- Unsigned units of 1/100th seconds of angle, in 2 octets
   -- values from 6000 to 65534 shall not be sent
   -- the value 65535 (0xFFFF) shall indicate an invalid value

SummerTime ::= ENUMERATED {
    notInSummerTime   (0),
    inSummerTime      (1)
    }
   -- Encoding as per above, in 1 bit

TenthSecond ::= INTEGER (0..9) 
   -- Unsigned units of 100 milliseconds, in 1 octet
   -- values from 10 to 254 shall not be sent
   -- the value 255 (0xFF) shall indicate an invalid value

TimeRemaining ::= INTEGER (0..9001)
    -- Unsigned units of 0.1 seconds, spanning 15 minutes, in 2 octets
    -- the value 9001 shall indicate 'forever'
    -- values from 9002 to 65534 shall not be sent
    -- the value 65535 (0xFFFF) shall indicate an invalid value

Year ::= INTEGER (1..65535)
   -- BCD coding of four digits of the year A.D. in 2 octets 
   -- values with nibble values between 1010 and 1111 shall not be sent
   -- except that the value 65535 (0xFFFF) shall indicate an invalid value

LatitudeDMS2 ::= SEQUENCE {
   d  DegreesLat,    -- units of degrees
   m  MinutesAngle,  -- units of minutes
   s  SecondsAngle   -- units of 1/100th seconds
   } -- total size of 4 octets (32 bits) when implicit encoding is used

LongitudeDMS2 ::= SEQUENCE {
   d  DegreesLong,   -- units of degrees
   m  MinutesAngle,  -- units of minutes
   s  SecondsAngle   -- units of 1/100th seconds
   } -- total size of 5 octets (40 bits) when implicit encoding is used

Node-LLdms-48b ::= SEQUENCE {
   lon  LongitudeDMS,
   lat  LatitudeDMS
   }

Node-LLdms-80b ::= SEQUENCE {
   lon  LongitudeDMS2,
   lat  LatitudeDMS2
   }

LaneDataAttribute-addGrpB ::= SEQUENCE { ... }

MovementEvent-addGrpB ::= SEQUENCE {
   -- A set of countdown style time-to-change values
   -- all in units of 0.1 seconds and following
   -- the naming of the base V2X standard

   startTime   TimeRemaining   OPTIONAL,
               -- When this phase 1st started
   minEndTime  MinTimetoChange,
               -- Expected shortest end time
   maxEndTime  MaxTimetoChange OPTIONAL,
               -- Expected longest end time
   likelyTime  TimeRemaining   OPTIONAL,
               -- Best predicted value based on other data             
   confidence  TimeIntervalConfidence   OPTIONAL,
               -- Applies to above time element only
   nextTime    TimeRemaining   OPTIONAL,
   ...
   }

NodeOffsetPointXY-addGrpB ::= CHOICE {
   -- Full position expressed in units of 0.01 seconds
   posA    Node-LLdms-48b,

   -- Full position expressed in multiple elements in
   -- an DD.MM.SS.sss style format
   posB    Node-LLdms-80b,

   ...
   }

Position3D-addGrpB ::= SEQUENCE {
   latitude     LatitudeDMS2,
   longitude    LongitudeDMS2,
   elevation    Elevation,
   ...
   }

TimeMark ::= SEQUENCE {
    year        Year,         -- BCD coding of A.D.    2 octets
    month       Month,        -- BCD coding of Month,  1 octet
    day         Day,          -- BCD coding of Day,    1 octet
    summerTime  SummerTime,
    holiday     Holiday,
    dayofWeek   DayOfWeek,
    hour        Hour,         -- BCD coding of Hour,   1 octet
    minute      Minute,       -- BCD coding of Minute, 1 octet
    second      Second,       -- BCD coding of Second, 1 octet
    tenthSecond TenthSecond   -- units of 100 millisecond, 1 octet
}
END
